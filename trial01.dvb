Attribute VB_Name = "FileReadModule"

Public Function OpenDialog(start_path As String)
    Dim fileName As String
    'Using the SendCommand method, send getfiled AutoLISP expressions to the AutoCAD command line.
    'Set the return value to a user-defined system variable USERS1.
    
    'resets users1 buffer
    ThisDrawing.SetVariable "users1", ""
    
    ThisDrawing.SendCommand "(setvar " & """users1""" & "(getfiled " & """Select a PaCAD File""" & """c:/program files/acad2012/""" & """PaCad""" & "8)) "
    ''ThisDrawing.SendCommand "(setvar " & """users1""" & "(getfiled " & """Select a text File""" & """c:/program files/acad2012/""" & """txt""" & "8)) "
    'Use the GetVariable method to retrieve this system variable to store the selected file name
    
    fileName = ThisDrawing.GetVariable("users1")
    If fileName = "" Then
        MsgBox "File not added."
        OpenDialog = ""
    Else
        MsgBox "You have selected " & fileName & "!!!", , "File Message"
        OpenDialog = fileName
    End If
End Function

Attribute VB_Name = "LineCase"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Dim cases As Variant
Dim name As String
Dim dict As Object


Public Function SetCases(input_ar As Variant)
    Set dict = CreateObject("Scripting.Dictionary")
    Dim id As Integer
    Dim tempValue As Variant
    
    id = 0
    For Each tempValue In input_ar
        id = id + 1
        dict.Add tempValue, id
    Next
End Function

Public Function PrintCases()
    Dim tempValue As Variant
    For Each tempValue In cases
        Debug.Print tempValue
    Next
End Function
Public Function GetId(key As String) As Integer
    If dict.Exists(key) Then
        GetId = dict(key)
    Else
        GetId = 0
    End If
End Function

Public Function GetId_(key As String) As Integer
    Dim id As Integer
    Dim tempValue As Variant
    id = 1
    For Each tempValue In cases
        If tempValue = key Then
            GetId = id
            Exit Function
        Else
            id = id + 1
        End If
    Next
    GetId = 0
End Function

Attribute VB_Name = "PaCADModule"
Public Sub PaCADImport()
    frmPaCADImport.show
    'Dim output As Double
    'output = ImportPaCAD(0, 0, "C:\Users\Young\Documents\vba_project\sample_data\newly_made.PaCAD")
    'output = ImportPaCAD(0, 0, "C:\Users\Young\Documents\vba_project\sample_data\AS-1.PaCAD")
End Sub
Public Function ImportPaCAD(nIndex As Integer, dbPrevRight As Double, strPaCADPath As String) As Double
    ' dbPrevRight -> 사용 위치 확인하기
    If Len(strPaCADPath) <= 0 Then
        frmPaCADImport.PrintOutput ("!! 실패 [" & str(nIndex) + "]-" & strPaCADPath)
        Exit Function
    End If
    
    Dim oAcadApp As Object
    Dim oAcadDoc As Object
    Dim oLayerObj As AcadLayer
    Set oAcadApp = GetObject(, "AutoCAD.Application")
    Set oAcadDoc = oAcadApp.ActiveDocument
    Dim fontSize As Double
    
    Dim nRealWidth_mm As Integer
    Dim nRealHeight_mm As Integer
    Dim dbRealLength_mm As Double
    Dim strVersion As String
    Dim visibleLength As Boolean
    Dim visibleWidth As Boolean
    
    Dim ncase As Integer
   
    Dim strLine As String
    Dim strValues() As String
    fontSize = Val(frmPaCADImport.TextBoxOutputGap.text)
    If fontSize < 0 Or fontSize > 1 Then
        fontSize = 0.03
    End If
    Call oAcadDoc.Layers.Add("TextLW")
    Call oAcadDoc.Layers.Add("TextA")
    
    
    enumNameSpace = 1
    enumVersion = 2
    enumTarget = 3
    enumManager = 4
    enumRealWidth = 5
    enumRealHeight = 6
    enumRealLength = 7
    enumVisibleLength = 8
    enumVisibleWidth = 9
    enumDefectUnit = 10
    enumDefect = 11

    Set lineHeaders = New LineCase
    headerValues = Array("^NameSpace", "^Version", "^Target", "^Manager", "^RealWidth" _
                        , "^RealHeight", "^RealLength", "^Visible_Length", "^Visible_Width" _
                        , "^DefectUnit", "^Defect")
    lineHeaders.SetCases headerValues

    ' start reading .PaCAD  ####
    Open strPaCADPath For Input As #1
    Do While Not EOF(1)
        Input #1, strLine
                            
        strValues = Split(strLine, "|")
        
        Dim nValueCount As Integer
        nValueCount = UBound(strValues) + 1     ' length of array "strValues"
        
        If nValueCount <= 0 Then
            Exit Do
        End If
        
        ncase = lineHeaders.GetId(strValues(0))
        If ncase = 0 Then
            Exit Do
        End If
                    
        Select Case ncase
            Case enumNameSpace
                If nValueCount = 2 Then
                    If strValues(1) = "PaCAD" Then
                    Else
                        Exit Do
                    End If
                End If
                
            Case enumVersion
                If nValueCount = 2 Then
                    strVersion = strValues(1)
                End If
                
            Case enumTarget
                            
            Case enumManager
                
            Case enumRealWidth
                If nValueCount = 2 Then
                    nRealWidth_mm = CInt(Val(strValues(1)))
                End If
                      
            Case enumRealHeight
                If nValueCount = 2 Then
                    nRealHeight_mm = CInt(Val(strValues(1)))
                End If
                
            Case enumRealLength
                If nValueCount = 2 Then
                    dbRealLength_mm = Val(strValues(1))
                End If
            
            Case enumVisibleLength
                If strValues(1) = "1" Then
                    visibleLength = True
                Else
                    visibleLength = False
                End If
            
            Case enumVisibleWidth
                If strValues(1) = "1" Then
                    visibleWidth = True
                Else
                    visibleWidth = False
                End If
            
            Case enumDefectUnit     ' Add defect layers
                If nValueCount = 2 Then
                
                    On Error Resume Next
                    strValues(1) = ReplaceAll(strValues(1), "/", "_")
                    
                    Call oAcadDoc.Layers(strValues(1))
                    If Err = 0 Then
                    Else
                        Err.Clear
                        Call oAcadDoc.Layers.Add(strValues(1))
                    End If
                End If
 
            Case CaseVar.Defect     ' &&&& Draw on a layer
                If nValueCount >= 4 Then
                
                    Dim dbVertices_m() As Double
                    Dim strPoints() As String
                    Dim oAcadLWPolyline As AcadLWPolyline
                    Dim textPos() As Double
                    Dim lastPosVal() As String
                    
                    Dim textKind As String
                    textKind = strValues(nValueCount - 2)
                    strValues(1) = ReplaceAll(strValues(1), "/", "_")
                    If textKind = "W" Then
                        ' ******** L, W
                        ' ### draw lines
                        Set oLayerObj = oAcadDoc.Layers(strValues(1))
                        oAcadDoc.ActiveLayer = oLayerObj
                        ReDim dbVertices_m(((nValueCount - 6) * 2) - 1) ' Not length but UBound value
                        
                        For i = 2 To nValueCount - 5    ' (nValueCount - 1) is last index
                            strPoints = Split(strValues(i), "*")
                            If (UBound(strPoints) + 1) = 2 Then
                                dbVertices_m((i - 2) * 2) = (Val(strPoints(0)) + dbPrevRight) * 0.001
                                dbVertices_m(((i - 2) * 2) + 1) = (Val(strPoints(1))) * 0.001
                            End If
                        Next i
                        
                        Set oAcadLWPolyline = oAcadDoc.ModelSpace.AddLightWeightPolyline(dbVertices_m)
                        oAcadLWPolyline.Closed = False
                        ' ### draw lines End
                        ' Draw Texts L, W
                        lastPosVal = Split(strValues(nValueCount - 5), "*")    ' pos of length
                        textPos = SetTextPos(lastPosVal, dbPrevRight)
                        Set oLayerObj = oAcadDoc.Layers("TextLW")
                        oAcadDoc.ActiveLayer = oLayerObj
                        oAcadDoc.ModelSpace.AddText "l:" & strValues(nValueCount - 3) & " w:" & strValues(nValueCount - 1), textPos, fontSize
                        ' ******** L, W End
                    ElseIf textKind = "A" Then
                        ' ******** A
                        ' ### draw lines
                        Set oLayerObj = oAcadDoc.Layers(strValues(1))
                        oAcadDoc.ActiveLayer = oLayerObj
                        ReDim dbVertices_m(((nValueCount - 4) * 2) - 1) ' Not length but UBound value
                        
                        For i = 2 To nValueCount - 3    ' (nValueCount - 1) is last index
                            strPoints = Split(strValues(i), "*")
                            If (UBound(strPoints) + 1) = 2 Then
                                dbVertices_m((i - 2) * 2) = (Val(strPoints(0)) + dbPrevRight) * 0.001
                                dbVertices_m(((i - 2) * 2) + 1) = (Val(strPoints(1))) * 0.001
                            End If
                        Next i
                        Set oAcadLWPolyline = oAcadDoc.ModelSpace.AddLightWeightPolyline(dbVertices_m)
                        oAcadLWPolyline.Closed = False
                        ' ### draw lines End
                    
                        ' Draw Texts Area
                        lastPosVal = Split(strValues(nValueCount - 3), "*")    ' pos of area
                        textPos = SetTextPos(lastPosVal, dbPrevRight)
                        Set oLayerObj = oAcadDoc.Layers("TextA")
                        oAcadDoc.ActiveLayer = oLayerObj
                        oAcadDoc.ModelSpace.AddText "a:" & strValues(nValueCount - 1), textPos, fontSize
                        ' ******** A End
                    Else
                        ' ******** Just lines
                        ' ### draw lines
                        Set oLayerObj = oAcadDoc.Layers(strValues(1))
                        oAcadDoc.ActiveLayer = oLayerObj
                        ReDim dbVertices_m(((nValueCount - 2) * 2) - 1) ' Not length but UBound value
                        
                        For i = 2 To nValueCount - 1    ' (nValueCount - 1) is last index
                            strPoints = Split(strValues(i), "*")
                            If (UBound(strPoints) + 1) = 2 Then
                                dbVertices_m((i - 2) * 2) = (Val(strPoints(0)) + dbPrevRight) * 0.001
                                dbVertices_m(((i - 2) * 2) + 1) = (Val(strPoints(1))) * 0.001
                            End If
                        Next i
                        Set oAcadLWPolyline = oAcadDoc.ModelSpace.AddLightWeightPolyline(dbVertices_m)
                        oAcadLWPolyline.Closed = False
                        ' ### draw lines End
                    
                End If
            ' &&&& Draw on a layer done.
            End If
        
        End Select
    Loop
    Close #1
    ' .PaCAD file close here    ####
    
    'PICBOX
    On Error Resume Next
    Set oLayerObj = oAcadDoc.Layers("PICBOX")
    If Err = 0 Then
    Else
        Err.Clear
        Set oLayerObj = oAcadDoc.Layers.Add("PICBOX")
    End If
                    
    'PICBOX 색상
    Dim aCol As AcadAcCmColor
    Set aCol = New AcadAcCmColor
    aCol.ColorMethod = acColorMethodByRGB
    aCol.ColorIndex = CLng(121)
    oLayerObj.TrueColor = aCol
    Set aCol = Nothing
    
    oAcadDoc.ActiveLayer = oLayerObj
    
    Dim nPicboxCount As Integer
    nPicboxCount = dbRealLength_mm / nRealHeight_mm
    If (dbRealLength_mm Mod nRealHeight_mm) > 0 Then
        nPicboxCount = nPicboxCount + 1
    End If
        
    For i = 0 To nPicboxCount - 1
        ReDim dbVertices_m(7)
5
        dbVertices_m(0) = dbPrevRight * 0.001
        dbVertices_m(1) = i * nRealHeight_mm * 0.001

        dbVertices_m(2) = (dbPrevRight + nRealWidth_mm) * 0.001
        dbVertices_m(3) = (i * nRealHeight_mm) * 0.001

        dbVertices_m(4) = (dbPrevRight + nRealWidth_mm) * 0.001
        dbVertices_m(5) = ((i * nRealHeight_mm) + nRealHeight_mm) * 0.001

        dbVertices_m(6) = dbPrevRight * 0.001
        dbVertices_m(7) = ((i * nRealHeight_mm) + nRealHeight_mm) * 0.001
        
        Set oAcadLWPolyline = oAcadDoc.ModelSpace.AddLightWeightPolyline(dbVertices_m)
        oAcadLWPolyline.Closed = True
        oAcadLWPolyline.Update
    Next i
        
    frmPaCADImport.PrintOutput ("성공 [" & str(nIndex) + "]-" & strPaCADPath)
    Debug.Print "Process done."
    
    ' 나중에 수정하기... -> TextBoxOutputGap parameter로 받아와야할듯
    ImportPaCAD = dbPrevRight + nRealWidth_mm + (Val(frmPaCADImport.TextBoxOutputGap.text) * 1000)
End Function

Function SetTextPos(pos() As String, adjustRight As Double) As Double()
    Dim textPos(0 To 2) As Double
    
    textPos(0) = (Val(pos(0)) + adjustRight) * 0.001
    textPos(1) = (Val(pos(1))) * 0.001
    textPos(2) = 0#
    SetTextPos = textPos
End Function

Function ReplaceAll(value As String, search As String, replacement As String) As String
    Dim tempValue As String
    tempValue = Replace(value, search, relacement)
    
    Do While Not StrComp(value, tempValue) = 0
    value = tempValue
    tempValue = Replace(value, search, replacement)
    Loop
    
    ReplaceAll = tempValue
End Function

Attribute VB_Name = "ThisDrawing"
Attribute VB_Base = "0{345D3165-3889-4694-AB75-A91A27B217E8}"
Attribute VB_GlobalNameSpace = False
Attribute VB_Creatable = False
Attribute VB_PredeclaredId = True
Attribute VB_Exposed = True
Attribute VB_TemplateDerived = False
Attribute VB_Customizable = True
Public Sub main()
    Output = ImportPaCAD(0, 0, "C:\Users\Young\Documents\vba_project\sample_data\양녕로_1.PaCAD")
End Sub

Attribute VB_Name = "frmPaCADImport"
Attribute VB_Base = "0{37323406-840B-4866-95A6-6D9A09F31CA9}{BED2528B-CB82-4847-B676-27489E68B9D6}"
Attribute VB_GlobalNameSpace = False
Attribute VB_Creatable = False
Attribute VB_PredeclaredId = True
Attribute VB_Exposed = False
Attribute VB_TemplateDerived = False
Attribute VB_Customizable = False
Private Sub CommandButton_ADD_Click()
    
    ''CommonDialog_ADD.Filter = "결함도 파일(*.PaCAD)|*.PaCAD|모든파일(*.*)|*.*"
    ''CommonDialog_ADD.ShowOpen
    Dim fileName As String
    fileName = OpenDialog("C:/")
    
    '파일을 추가한다.
    If Len(fileName) <> 0 Then
    
        Dim nSelectIndex As Integer
        Dim nListSize As Integer
        Dim strPaCADPaths() As String
                
        nListSize = ListBox_PaCAD.ListCount
        nSelectIndex = 0
        
        ' 이전데이터를 저장한다.
        If nListSize > 0 Then
            nSelectIndex = ListBox_PaCAD.ListIndex
            If nSelectIndex < 0 Then
                nSelectIndex = nListSize - 1
            End If
                    
            Dim i As Integer
            ReDim strPaCADPaths(nListSize)
            For i = 0 To nListSize - 1
                strPaCADPaths(i) = ListBox_PaCAD.List(i)
            Next i
        End If
        
        ListBox_PaCAD.Clear
                    
        '리스트박스에 다시 데이터를 넣는다.
        If nListSize = 0 Then
            ListBox_PaCAD.AddItem (fileName)
            ListBox_PaCAD.ListIndex = 0
        Else
            For i = 0 To nListSize
               If i = nSelectIndex + 1 Then
                     ListBox_PaCAD.AddItem (fileName)
                ElseIf i > nSelectIndex + 1 Then
                    ListBox_PaCAD.AddItem (strPaCADPaths(i - 1))
                Else
                    ListBox_PaCAD.AddItem (strPaCADPaths(i))
                End If
            Next i
            
            ListBox_PaCAD.ListIndex = nSelectIndex + 1
        End If
                
    End If
   
End Sub
Private Sub CommandButton_DEL_Click()
    
    If ListBox_PaCAD.ListIndex < 0 Then
        MsgBox "리스트에서 삭제할 파일을 선택하세요."
        Exit Sub
    End If
    
    ListBox_PaCAD.RemoveItem (ListBox_PaCAD.ListIndex)
    
End Sub


Private Sub CommandButton_UP_Click()
    
    If ListBox_PaCAD.ListIndex < 1 Then
       Exit Sub
    End If
    
    Dim nSelectIndex As Integer
    Dim nListSize As Integer
    Dim strPaCADPaths() As String
            
    nListSize = ListBox_PaCAD.ListCount
    nSelectIndex = ListBox_PaCAD.ListIndex
    
    ' 이전데이터를 저장한다.
    If nListSize > 0 Then
        Dim i As Integer
        ReDim strPaCADPaths(nListSize)
        For i = 0 To nListSize - 1
            strPaCADPaths(i) = ListBox_PaCAD.List(i)
        Next i
    End If
    
    ListBox_PaCAD.Clear
        
    '리스트박스에 다시 데이터를 넣는다.
    For i = 0 To nListSize - 1
       If i = nSelectIndex - 1 Then
             ListBox_PaCAD.AddItem (strPaCADPaths(nSelectIndex))
        ElseIf i = nSelectIndex Then
            ListBox_PaCAD.AddItem (strPaCADPaths(nSelectIndex - 1))
        Else
            ListBox_PaCAD.AddItem (strPaCADPaths(i))
        End If
    Next i
    
    ListBox_PaCAD.ListIndex = nSelectIndex - 1
        
End Sub
Private Sub CommandButton_DOWN_Click()

    If ListBox_PaCAD.ListIndex < 0 Then
       Exit Sub
    End If
    
    If ListBox_PaCAD.ListIndex >= ListBox_PaCAD.ListCount - 1 Then
       Exit Sub
    End If
    
    Dim nSelectIndex As Integer
    Dim nListSize As Integer
    Dim strPaCADPaths() As String
            
    nListSize = ListBox_PaCAD.ListCount
    nSelectIndex = ListBox_PaCAD.ListIndex
    
    ' 이전데이터를 저장한다.
    If nListSize > 0 Then
        Dim i As Integer
        ReDim strPaCADPaths(nListSize)
        For i = 0 To nListSize - 1
            strPaCADPaths(i) = ListBox_PaCAD.List(i)
        Next i
    End If
    
    ListBox_PaCAD.Clear
        
    '리스트박스에 다시 데이터를 넣는다.
    For i = 0 To nListSize - 1
       If i = nSelectIndex + 1 Then
             ListBox_PaCAD.AddItem (strPaCADPaths(nSelectIndex))
        ElseIf i = nSelectIndex Then
            ListBox_PaCAD.AddItem (strPaCADPaths(nSelectIndex + 1))
        Else
            ListBox_PaCAD.AddItem (strPaCADPaths(i))
        End If
    Next i
    
    ListBox_PaCAD.ListIndex = nSelectIndex + 1
End Sub
Private Sub CommandButton_IMPORT_Click()

    If ListBox_PaCAD.ListCount <= 0 Then
       MsgBox "결함도 파일이 리스트에 존재하지 않습니다."
       Exit Sub
    End If
    
    Call PrintOutput("----------------------------")
    Call PrintOutput("Import 시작")
    
    Dim dbPrevRight As Double

    Dim i As Integer
    For i = 0 To ListBox_PaCAD.ListCount - 1
        Dim strPaCADPath As String
        strPaCADPath = ListBox_PaCAD.List(i)
        dbPrevRight = ImportPaCAD(i, dbPrevRight, strPaCADPath)
    Next i
    
    Call PrintOutput("Import 종료")
End Sub
Public Sub PrintOutput(strOutput As String)

    If ListBox_OUTPUT.ListCount > 20 Then
        ListBox_OUTPUT.RemoveItem (0)
    End If
        
    ListBox_OUTPUT.AddItem (strOutput)
    ListBox_OUTPUT.ListIndex = ListBox_OUTPUT.ListCount - 1
    
End Sub

Private Sub frmPaCADImport_Click()

End Sub

Private Sub Label1_Click()

End Sub

Private Sub Label2_Click()

End Sub

Private Sub ListBox_PaCAD_Click()

End Sub

Private Sub TextBoxFontSize_Change()

End Sub

Private Sub TextBoxOutputGap_Change()

End Sub

Private Sub UserForm_Click()

End Sub
