Attribute VB_Name = "FileManager"
Public Function OpenDialog(start_path As String)
    Dim fileName As String
    'Using the SendCommand method, send getfiled AutoLISP expressions to the AutoCAD command line.
    'Set the return value to a user-defined system variable USERS1.
    
    'resets users1 buffer
    ThisDrawing.SetVariable "users1", ""
    
    ThisDrawing.SendCommand "(setvar " & """users1""" & "(getfiled " & """Select a PaCAD File""" & """c:/program files/acad2012/""" & """PaCad""" & "8)) "
    ''ThisDrawing.SendCommand "(setvar " & """users1""" & "(getfiled " & """Select a text File""" & """c:/program files/acad2012/""" & """txt""" & "8)) "
    'Use the GetVariable method to retrieve this system variable to store the selected file name
    
    fileName = ThisDrawing.GetVariable("users1")
    If fileName = "" Then
        MsgBox "File not added."
        OpenDialog = ""
    Else
        MsgBox "You have selected " & fileName & "!!!", , "File Message"
        OpenDialog = fileName
    End If
End Function

Attribute VB_Name = "PaCADModule"
Public Sub PaCADImport()

    frmPaCADImport.show
    
End Sub
Public Function ImportPaCAD(nIndex As Integer, dbPrevRight As Double, strPaCADPath As String) As Double
        
    If Len(strPaCADPath) <= 0 Then
        frmPaCADImport.PrintOutput ("!! 실패 [" & Str(nIndex) + "]-" & strPaCADPath)
        Exit Function
    End If
            
    Dim oAcadApp As Object
    Dim oAcadDoc As Object
    Dim oLayerObj As AcadLayer
    Set oAcadApp = GetObject(, "AutoCAD.Application")
    Set oAcadDoc = oAcadApp.ActiveDocument
    
    Dim nRealWidth_mm As Integer
    Dim nRealHeight_mm As Integer
    Dim dbRealLength_mm As Double
    Dim strVersion As String
    
    Dim nCase As Integer
    Dim nCase_NameSpace As String
    Dim nCase_Version As Double
    Dim nCase_Target As String
    Dim nCase_Manager As String
    Dim nCase_RealWidth As Integer
    Dim nCase_RealHeight As Integer
    Dim nCase_RealLength As Integer
    Dim nCase_DefectUnit As Integer
    Dim nCase_Defect As Integer
    
    nCase = 0
    nCase_NameSpace = nCase + 1
    nCase_Version = nCase_NameSpace + 1
    nCase_Target = nCase_Version + 1
    nCase_Manager = nCase_Target + 1
    nCase_RealWidth = nCase_Manager + 1
    nCase_RealHeight = nCase_RealWidth + 1
    nCase_RealLength = nCase_RealHeight + 1
    nCase_DefectUnit = nCase_RealLength + 1
    nCase_Defect = nCase_DefectUnit + 1
    
    Dim strLine As String
    Dim strValue() As String
    
    Open strPaCADPath For Input As #1
    Do While Not EOF(1)
        Input #1, strLine
                            
        strValue = Split(strLine, "|")
        
        Dim nValueCount As Integer
        nValueCount = UBound(strValue) + 1
        
        If nValueCount <= 0 Then
            Exit Do
        End If
            
        nCase = 0
        If strValue(0) = "^NameSpace" Then
            nCase = nCase_NameSpace
        ElseIf strValue(0) = "^Version" Then
            nCase = nCase_Version
        ElseIf strValue(0) = "^Target" Then
            nCase = nCase_Target
        ElseIf strValue(0) = "^Manager" Then
            nCase = nCase_Manager
        ElseIf strValue(0) = "^RealWidth" Then
            nCase = nCase_RealWidth
        ElseIf strValue(0) = "^RealHeight" Then
            nCase = nCase_RealHeight
        ElseIf strValue(0) = "^RealLength" Then
            nCase = nCase_RealLength
        ElseIf strValue(0) = "^DefectUnit" Then
            nCase = nCase_DefectUnit
        ElseIf strValue(0) = "^Defect" Then
            nCase = nCase_Defect
        End If
                    
        If nCase = 0 Then
            Exit Do
        End If
                    
        Select Case nCase
            Case nCase_NameSpace
                If nValueCount = 2 Then
                    If strValue(1) = "PaCAD" Then
                    Else
                        Exit Do
                    End If
                End If
                
            Case nCase_Version
                If nValueCount = 2 Then
                    strVersion = strValue(1)
                End If
                
            Case nCase_Target
                            
            Case nCase_Manager
                
            Case nCase_RealWidth
                If nValueCount = 2 Then
                    nRealWidth_mm = CInt(Val(strValue(1)))
                End If
                      
            Case nCase_RealHeight
                If nValueCount = 2 Then
                    nRealHeight_mm = CInt(Val(strValue(1)))
                End If
                
            Case nCase_RealLength
                If nValueCount = 2 Then
                    dbRealLength_mm = Val(strValue(1))
                End If
                        
            Case nCase_DefectUnit
                If nValueCount = 2 Then
                
                    On Error Resume Next
                    
                    Dim strValueTemp As String
                    strValueTemp = Replace(strValue(1), "/", "_")
                    
                    Do While Not StrComp(strValueTemp, strValue(1)) = 0
                        strValue(1) = strValueTemp
                        strValueTemp = Replace(strValue(1), "/", "_")
                    Loop
                    
                    Set oLayerObj = oAcadDoc.Layers(strValue(1))
                    If Err = 0 Then
                    Else
                        Err.Clear
                        Set oLayerObj = oAcadDoc.Layers.Add(strValue(1))
                    End If
                End If

            Case nCase_Defect
                If nValueCount >= 4 Then
                    On Error Resume Next
                    
                    Dim strValueTemp2 As String
                    strValueTemp2 = Replace(strValue(1), "/", "_")
                    
                    Do While Not StrComp(strValueTemp2, strValue(1)) = 0
                        strValue(1) = strValueTemp2
                        strValueTemp2 = Replace(strValue(1), "/", "_")
                    Loop
                    
                    Set oLayerObj = oAcadDoc.Layers(strValue(1))
                    If Err = 0 Then
                    
                        oAcadDoc.ActiveLayer = oLayerObj
                        Dim dbVertices_m() As Double
                        Dim nPointCount As Integer
                        nPointCount = ((nValueCount - 2) * 2) - 1
                        ReDim dbVertices_m(nPointCount)
                    
                        For i = 2 To nValueCount - 1
                            Dim strPoints() As String
                            strPoints = Split(strValue(i), "*")
                            
                            Dim nPointCountValue As Integer
                            nPointCountValue = UBound(strPoints) + 1
                            
                            If nPointCountValue = 2 Then
                            
                                dbVertices_m((i - 2) * 2) = (Val(strPoints(0)) + dbPrevRight) * 0.001
                                dbVertices_m(((i - 2) * 2) + 1) = (Val(strPoints(1))) * 0.001
                                
                            End If
                        Next i
                        
                        Dim oAcadLWPolyline As AcadLWPolyline
                        Set oAcadLWPolyline = oAcadDoc.ModelSpace.AddLightWeightPolyline(dbVertices_m)
                        oAcadLWPolyline.Closed = False
                    End If
                    
                    
                End If
        
        End Select
    Loop
    Close #1
    
    'PICBOX
    On Error Resume Next
    Set oLayerObj = oAcadDoc.Layers("PICBOX")
    If Err = 0 Then
    Else
        Err.Clear
        Set oLayerObj = oAcadDoc.Layers.Add("PICBOX")
    End If
                    
    'PICBOX 색상
    Dim aCol As AcadAcCmColor
    Set aCol = New AcadAcCmColor
    aCol.ColorMethod = acColorMethodByRGB
    aCol.ColorIndex = CLng(121)
    oLayerObj.TrueColor = aCol
    Set aCol = Nothing
    
    oAcadDoc.ActiveLayer = oLayerObj
                    
    Dim nPicboxCount As Integer
    nPicboxCount = dbRealLength_mm / nRealHeight_mm
    If (dbRealLength_mm Mod nRealHeight_mm) > 0 Then
        nPicboxCount = nPicboxCount + 1
    End If
        
    For i = 0 To nPicboxCount - 1
        ReDim dbVertices_m(7)
        
        dbVertices_m(0) = dbPrevRight * 0.001
        dbVertices_m(1) = i * nRealHeight_mm * 0.001

        dbVertices_m(2) = (dbPrevRight + nRealWidth_mm) * 0.001
        dbVertices_m(3) = (i * nRealHeight_mm) * 0.001

        dbVertices_m(4) = (dbPrevRight + nRealWidth_mm) * 0.001
        dbVertices_m(5) = ((i * nRealHeight_mm) + nRealHeight_mm) * 0.001

        dbVertices_m(6) = dbPrevRight * 0.001
        dbVertices_m(7) = ((i * nRealHeight_mm) + nRealHeight_mm) * 0.001
        
        Set oAcadLWPolyline = oAcadDoc.ModelSpace.AddLightWeightPolyline(dbVertices_m)
        oAcadLWPolyline.Closed = True
        oAcadLWPolyline.Update
    Next i
        
    frmPaCADImport.PrintOutput ("성공 [" & Str(nIndex) + "]-" & strPaCADPath)
        
    ImportPaCAD = dbPrevRight + nRealWidth_mm + (Val(frmPaCADImport.TextBoxOutputGap.Text) * 1000)
End Function

Attribute VB_Name = "frmPaCADImport"
Attribute VB_Base = "0{DEBF6FB9-3233-444C-9497-FC02BD7CD21A}{9AEF5FFC-B22D-49CB-9CC8-A85EE2F6F3B2}"
Attribute VB_GlobalNameSpace = False
Attribute VB_Creatable = False
Attribute VB_PredeclaredId = True
Attribute VB_Exposed = False
Attribute VB_TemplateDerived = False
Attribute VB_Customizable = False
Private Sub CommandButton_ADD_Click()
    
    ''CommonDialog_ADD.Filter = "결함도 파일(*.PaCAD)|*.PaCAD|모든파일(*.*)|*.*"
    ''CommonDialog_ADD.ShowOpen
    Dim fileName As String
    fileName = OpenDialog("C:/")
    
    '파일을 추가한다.
    If Len(fileName) <> 0 Then
    
        Dim nSelectIndex As Integer
        Dim nListSize As Integer
        Dim strPaCADPaths() As String
                
        nListSize = ListBox_PaCAD.ListCount
        nSelectIndex = 0
        
        ' 이전데이터를 저장한다.
        If nListSize > 0 Then
            nSelectIndex = ListBox_PaCAD.ListIndex
            If nSelectIndex < 0 Then
                nSelectIndex = nListSize - 1
            End If
                    
            Dim i As Integer
            ReDim strPaCADPaths(nListSize)
            For i = 0 To nListSize - 1
                strPaCADPaths(i) = ListBox_PaCAD.List(i)
            Next i
        End If
        
        ListBox_PaCAD.Clear
                    
        '리스트박스에 다시 데이터를 넣는다.
        If nListSize = 0 Then
            ListBox_PaCAD.AddItem (fileName)
            ListBox_PaCAD.ListIndex = 0
        Else
            For i = 0 To nListSize
               If i = nSelectIndex + 1 Then
                     ListBox_PaCAD.AddItem (fileName)
                ElseIf i > nSelectIndex + 1 Then
                    ListBox_PaCAD.AddItem (strPaCADPaths(i - 1))
                Else
                    ListBox_PaCAD.AddItem (strPaCADPaths(i))
                End If
            Next i
            
            ListBox_PaCAD.ListIndex = nSelectIndex + 1
        End If
                
    End If
   
End Sub
Private Sub CommandButton_DEL_Click()
    
    If ListBox_PaCAD.ListIndex < 0 Then
        MsgBox "리스트에서 삭제할 파일을 선택하세요."
        Exit Sub
    End If
    
    ListBox_PaCAD.RemoveItem (ListBox_PaCAD.ListIndex)
    
End Sub


Private Sub CommandButton_UP_Click()
    
    If ListBox_PaCAD.ListIndex < 1 Then
       Exit Sub
    End If
    
    Dim nSelectIndex As Integer
    Dim nListSize As Integer
    Dim strPaCADPaths() As String
            
    nListSize = ListBox_PaCAD.ListCount
    nSelectIndex = ListBox_PaCAD.ListIndex
    
    ' 이전데이터를 저장한다.
    If nListSize > 0 Then
        Dim i As Integer
        ReDim strPaCADPaths(nListSize)
        For i = 0 To nListSize - 1
            strPaCADPaths(i) = ListBox_PaCAD.List(i)
        Next i
    End If
    
    ListBox_PaCAD.Clear
        
    '리스트박스에 다시 데이터를 넣는다.
    For i = 0 To nListSize - 1
       If i = nSelectIndex - 1 Then
             ListBox_PaCAD.AddItem (strPaCADPaths(nSelectIndex))
        ElseIf i = nSelectIndex Then
            ListBox_PaCAD.AddItem (strPaCADPaths(nSelectIndex - 1))
        Else
            ListBox_PaCAD.AddItem (strPaCADPaths(i))
        End If
    Next i
    
    ListBox_PaCAD.ListIndex = nSelectIndex - 1
        
End Sub
Private Sub CommandButton_DOWN_Click()

    If ListBox_PaCAD.ListIndex < 0 Then
       Exit Sub
    End If
    
    If ListBox_PaCAD.ListIndex >= ListBox_PaCAD.ListCount - 1 Then
       Exit Sub
    End If
    
    Dim nSelectIndex As Integer
    Dim nListSize As Integer
    Dim strPaCADPaths() As String
            
    nListSize = ListBox_PaCAD.ListCount
    nSelectIndex = ListBox_PaCAD.ListIndex
    
    ' 이전데이터를 저장한다.
    If nListSize > 0 Then
        Dim i As Integer
        ReDim strPaCADPaths(nListSize)
        For i = 0 To nListSize - 1
            strPaCADPaths(i) = ListBox_PaCAD.List(i)
        Next i
    End If
    
    ListBox_PaCAD.Clear
        
    '리스트박스에 다시 데이터를 넣는다.
    For i = 0 To nListSize - 1
       If i = nSelectIndex + 1 Then
             ListBox_PaCAD.AddItem (strPaCADPaths(nSelectIndex))
        ElseIf i = nSelectIndex Then
            ListBox_PaCAD.AddItem (strPaCADPaths(nSelectIndex + 1))
        Else
            ListBox_PaCAD.AddItem (strPaCADPaths(i))
        End If
    Next i
    
    ListBox_PaCAD.ListIndex = nSelectIndex + 1
End Sub
Private Sub CommandButton_IMPORT_Click()

    If ListBox_PaCAD.ListCount <= 0 Then
       MsgBox "결함도 파일이 리스트에 존재하지 않습니다."
       Exit Sub
    End If
    
    Call PrintOutput("----------------------------")
    Call PrintOutput("Import 시작")
    
    Dim dbPrevRight As Double
    nPrevRight = 0
    
    Dim i As Integer
    For i = 0 To ListBox_PaCAD.ListCount - 1
        Dim strPaCADPath As String
        strPaCADPath = ListBox_PaCAD.List(i)
        dbPrevRight = ImportPaCAD(i, dbPrevRight, strPaCADPath)
    Next i
    
    Call PrintOutput("Import 종료")
End Sub
Public Sub PrintOutput(strOutput As String)

    If ListBox_OUTPUT.ListCount > 20 Then
        ListBox_OUTPUT.RemoveItem (0)
    End If
        
    ListBox_OUTPUT.AddItem (strOutput)
    ListBox_OUTPUT.ListIndex = ListBox_OUTPUT.ListCount - 1
    
End Sub

Private Sub frmPaCADImport_Click()

End Sub

Private Sub ListBox_PaCAD_Click()

End Sub

Private Sub TextBoxOutputGap_Change()

End Sub

Private Sub UserForm_Click()

End Sub
