Attribute VB_Name = "ThisDrawing"
Attribute VB_Base = "0{345D3165-3889-4694-AB75-A91A27B217E8}"
Attribute VB_GlobalNameSpace = False
Attribute VB_Creatable = False
Attribute VB_PredeclaredId = True
Attribute VB_Exposed = True
Attribute VB_TemplateDerived = False
Attribute VB_Customizable = True
Sub main()
    Dim str As String
    Dim myArr() As String
    Dim numbers() As Integer
    ReDim numbers(10)
    Dim tempCount As Integer
    tempCount = 0
    
    For Each ele In numbers
        Debug.Print tempCount
        tempCount = tempCount + 1
    Next ele
    
    
    
End Sub
